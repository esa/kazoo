Lift-dataview DEFINITIONS ::=
BEGIN

UpDown		::= ENUMERATED { up (1),   down (0)  }
OnOff		::= ENUMERATED { on (1),   off (0)   }
OpenClose	::= ENUMERATED { door-open (1), door-close (0) }
Position	::= REAL (-100 .. 100.0)
Floors		::= INTEGER { 
			floor-0 (0), 
			floor-1 (10), 
			floor-2 (20), 
			floor-3 (30), 
			floor-4 (40), 
			floor-5 (50) 
		    } (0 | 10 | 20 | 30 | 40 | 50)

-- Types used for the interfacing with the Simulink model

Lift-control ::= SEQUENCE {
    direction	UpDown DEFAULT down,
    motor	OnOff  DEFAULT on,
    brake	OnOff  DEFAULT off,
    door	OpenClose
}

Lift-sensor ::= SEQUENCE {
    door-open	    BOOLEAN,
    door-closed	    BOOLEAN,
    floor-detected  BOOLEAN,
    pos-x	    Position
}

-- Types used for the user interaction

Floor-button ::= SEQUENCE {
    floor	Floors,
    direction	UpDown
}

Cabin-button ::= CHOICE {
    emergency-stop  BOOLEAN,
    floor	    Floors
}

Start-condition ::= CHOICE {
	forever     BOOLEAN,
	nb-of-cycle INTEGER (50 .. 255)
}

Status ::= SEQUENCE {
   lift Lift-sensor,
   door OpenClose
}

END
