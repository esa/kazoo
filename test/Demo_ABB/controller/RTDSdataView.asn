Lift-dataview DEFINITIONS ::=
BEGIN

UpDown		::= ENUMERATED { up (1),   down (0)  }
OnOff		::= ENUMERATED { on (1),   off (0)   }
OpenClose	::= ENUMERATED { door-open (1), door-close (0) }
Position	::= REAL (0.0 .. 100.0)
Flag		::= BOOLEAN
Floors		::= ENUMERATED { 
			floor-0 (10), 
			floor-1 (20), 
			floor-2 (30), 
			floor-3 (40), 
			floor-4 (50), 
			floor-5 (60),
			floor-above (70) 
		    }

-- Types used for the interfacing with the Simulink model

Lift-control ::= SEQUENCE {
    direction	UpDown,
    motor	OnOff,
    brake	OnOff,
    door	OpenClose
}

Lift-sensor ::= SEQUENCE {
    door-open	    Flag,
    door-closed	    Flag,
    floor-detected  Flag,
    pos-x	    Position
}

-- Types used for the user interaction

Floor-button ::= SEQUENCE {
    floor	Floors,
    direction	UpDown
}

Cabin-button ::= CHOICE {
    emergency-stop  Flag,
    floor	    Floors
}

Start-condition ::= CHOICE {
	forever BOOLEAN,
	nb-of-cycle INTEGER (1..255)
}
    

END
