DataView DEFINITIONS AUTOMATIC TAGS ::= BEGIN

Display-T ::= OCTET STRING (SIZE (1..255))

Action-T ::= CHOICE 
{
    --display INTEGER (0..255),
    display Display-T,
    other-action INTEGER (0..1),
    housekeeping Destination-T
}

Destination-T ::= ENUMERATED { displayer(0), other-dest(1) }

TC-T ::= SEQUENCE 
{
    destination Destination-T,
    action Action-T DEFAULT display:'48656C6C6F'H
}

TM-T ::= Display-T

HK-T ::= SEQUENCE {
    value-to-plot INTEGER (0..16535) DEFAULT 42,
    destination Destination-T
}
END
