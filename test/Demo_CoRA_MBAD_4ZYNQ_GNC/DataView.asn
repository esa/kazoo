TASTE-Dataview DEFINITIONS ::=
BEGIN
IMPORTS T-Int32, T-UInt32, T-Int8, T-UInt8, T-Boolean FROM TASTE-BasicTypes;

TASTE-Boolean ::= BOOLEAN

-- ASN.1 Type definitions must start with an uppercase
-- Field names in records (SEQUENCE) must start with a lowercase
-- Underscores are not allowed: use dash (hyphen) 

MyInteger::= INTEGER (-411673351.. 763937697)
-- MyReal      ::= REAL (0.0 .. 10.0)

Seq3     ::= SEQUENCE (SIZE (3)) OF MyInteger
Seq4     ::= SEQUENCE (SIZE (4)) OF MyInteger
Seqout     ::= SEQUENCE (SIZE (8)) OF MyInteger

In-Nested      ::= SEQUENCE {
      inest-a  SEQUENCE (SIZE (4)) OF T-Int32,
      inest-b  SEQUENCE (SIZE (3)) OF T-Int32
}

Out-Nested       ::= SEQUENCE {
     onest-a SEQUENCE (SIZE (7)) OF T-Int32
}

-- Simple types:

-- MyInteger   ::= INTEGER (0..255)
-- MyReal      ::= REAL (0.0 .. 1000.0)
-- MyBool      ::= BOOLEAN
-- MyEnum      ::= ENUMERATED { hello, world, how-are-you }

-- Complex types:

--  MySeq       ::= SEQUENCE {
--      input-data  MyInteger,
--      output-data MyInteger,
--      validity    ENUMERATED { valid, invalid }
--  }
--
--  MyChoice    ::= CHOICE {
--      a BOOLEAN,
--      b MySeq
--  }
--
--  MySeqOf     ::= SEQUENCE (SIZE (2)) OF MyEnum
--
--  MyOctStr    ::= OCTET STRING (SIZE (3))
--
--  -- You can also declare constants
--  myVar       MySeqOf     ::= { hello, world }

END
