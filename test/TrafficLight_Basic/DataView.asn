TRAFFICLIGHT-BASIC-DATAVIEW DEFINITIONS ::=
BEGIN
IMPORTS T-Int32, T-UInt32, T-Int8, T-UInt8, T-Boolean FROM TASTE-BasicTypes;

   TL-Color ::= ENUMERATED { red, orange, green}


    P-Light ::= ENUMERATED { go, wait }

    Command ::= ENUMERATED { request-passage }

END
